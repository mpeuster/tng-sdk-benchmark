/*
*  Copyright (c) 2019 Manuel Peuster <manuel@peuster.de
*  Copyright (c) 2019 SONATA-NFV, 5GTANGO, Paderborn University
* ALL RIGHTS RESERVED.
*
* Licensed under the Apache License, Version 2.0 (the "License");
* you may not use this file except in compliance with the License.
* You may obtain a copy of the License at
*
*     http://www.apache.org/licenses/LICENSE-2.0
*
* Unless required by applicable law or agreed to in writing, software
* distributed under the License is distributed on an "AS IS" BASIS,
* WITHOUT WARRANTIES OR CONDITIONS OF ANY KIND, either express or implied.
* See the License for the specific language governing permissions and
* limitations under the License.
*
* Neither the name of the SONATA-NFV, 5GTANGO, Paderborn University
* nor the names of its contributors may be used to endorse or promote
* products derived from this software without specific prior written
* permission.
*
* This work has also been performed in the framework of the 5GTANGO project,
* funded by the European Commission under Grant number 761493 through
* the Horizon 2020 and 5G-PPP programmes. The authors would like to
* acknowledge the contributions of their colleagues of the SONATA
* partner consortium (www.5gtango.eu).
*/
module ietf-ped-catalog
{
  namespace "urn:ietf:params:xml:ns:yang:ietf-ped-catalog";
  prefix "pe";
  // Additional types (see RFC6021)
  //import "ietf-yang-types" {
  //  prefix "ietf";
  //}
  import "ietf-inet-types" {
    prefix "inet";
  }
  organization "Paderborn University";
  contact "Manuel Peuster <manuel@peuster.de>";
  description "Performance Experiment Descriptor (PED) model";

  revision 2019-03-08 {
    description
      "Initial revision. This YANG file defines
       the Performance Experiment Descriptor (PED)";
    reference ""; 
  }

  typedef time-in-seconds {
         type uint64;
         units "seconds (s)";
         default 0;
         description "A time value.";
  }

  // --- 
  // Generic re-usable structures.
  // ---
  grouping vendor-name-version-id-ref {
    description "Reference (vendor.name.version triple) to another artefact/object.";
    leaf vendor-ref {
      type string{
        length "1..255";
        pattern "^[a-z0-9\\-_.]+$";
      }
      mandatory true;
      description "Vendor part of the reference";
    }
    leaf name-ref {
      type string{
        length "1..255";
        pattern "^[a-z0-9\\-_.]+$";
      }
      mandatory true;
      description "Name part of the reference";
    }
    leaf version-ref {
      type string {
        length "1..32";
        pattern "^[abv0-9\\-_.]+$";
      }
      mandatory true;
      description "Version part of the reference";
    }
  }

  grouping generic-description {
    description "Generic description text";
    leaf description {
      type string;
      description "Generic description text";
    }
  }

  grouping expandable-parameter-float {
    description "Expandable numeric parameter which can either hold
    a single value (scalar), a list of values (vector), or a definition
    of a loop (w. begin, end, step parameter). These expandable
    parameters can be used to define complex parameter studies.";
    choice parameter {
      case scalar {
        leaf scalar {
          type decimal64{
              fraction-digits 4;
          }
          mandatory true;
          description "Single numeric value";
        }
      }
      case vector {
        leaf-list vector {
          type decimal64{
              fraction-digits 4;
          }
          min-elements 1;
          description "List of numeric values";
        }
      }
      case loop {
        container loop {
          leaf begin {
            type decimal64{
              fraction-digits 4;
            }
            mandatory true;
            description "Start value of the loop";
          }
          leaf end {
            type decimal64{
              fraction-digits 4;
            }
            mandatory true;
            description "Stop value of the loop";
          }
          leaf step {
            type decimal64{
              fraction-digits 4;
            }
            description "Step size of the loop";
          }
          description "Loop that generates a list of numeric values";
        }
      }
      mandatory true;
      description "Choice: scalar, vector, loop";
    }
  }

  grouping expandable-parameter-string {
    description "Expandable string parameter which can either hold
    a single value (scalar) or a list of values (vector). These
    expandable parameters can be used to define complex parameter
    studies.";
    choice parameter {
      case scalar {
        leaf scalar {
          type string;
          mandatory true;
          description "Single string value";
        }
      }
      case vector {
        leaf-list vector {
          type string;
          min-elements 1;
          description "List of string values";
        }
      }
      mandatory true;
      description "Choice: scalar or vector";
    }
  }

  // --- 
  // PED-specific structures.
  // ---
  grouping sut-ref {
    description "Reference to a system under test (SUT).
    Reference is given by a vendor.name.version triple.
    Additionally a URI can be specified, e.g., to point
    to a VNF or network service package that contains
    the SUT.";
    leaf id {
      type string{
        length "1..255";
        pattern "^[a-z0-9\\-_.]+$";
      }
      mandatory true;
      description "SUT identifier";
    }
    leaf uri {
      type inet:uri;
      description "Path/URL pointing to the SUT's location";
    }
    uses vendor-name-version-id-ref;
    uses generic-description;
  }

  grouping probe {
    description "Additional stimulation/measruement component
    to test the SUT. References a container image which is used
    to deploy and run the probe.";
    leaf id {
      type string{
        length "1..255";
        pattern "^[a-z0-9\\-_.]+$";
      }
      mandatory true;
      description "Probe identifier";
    }
    leaf container-image {
      type string;
      mandatory true;
      description "Name of the container image to be used for this probe";
    }
    leaf connection-point-ref {
      type string{
        length "1..255";
        pattern "^[a-z0-9\\-_.:]+$";
      }
      description "Name of SUT connectin point to which this probe should be connected (same as specified in the SUT's VNF/NS descriptor)";
    }
    leaf address {
      type inet:ipv4-prefix;
      description "Static address the probe should get on its data iterface (CIDR)";
    }
  }

  grouping node-command-parameter {
    description "Set of parameters to configure node start and stop commands";
    container cmd-start {
      description "Command(s) executed after node instantiation";
      uses expandable-parameter-string;
    }
    container cmd-stop {
      description "Command(s) executed before node termination";
      uses expandable-parameter-string;
    }
  }

  grouping node-resource-parameter {
    description "Set of parameters to configure node resources";
    container cpu-bw {
      description "CPU bandwidth (CPU time fraction 0...1.0)";
      uses expandable-parameter-float;
    }
    container cpu-core-set {
      description "CPU core set to be used, e.g., core 1 and 3: '1,3'";
      uses expandable-parameter-string;
    }
    container mem-max {
      description "Memory limit in MB";
      uses expandable-parameter-float;
    }
    container mem-swap-max {
      description "Momory swap limit in MB (not implemented yet)";
      uses expandable-parameter-float;
    }
    container io-bw {
      description "IO bandwidth limit (not implemented yet)";
      uses expandable-parameter-float;
    }
  }

  grouping experiment {
    description "Definition of a single performance experiment";
    leaf id {
      type string{
        length "1..255";
        pattern "^[a-z0-9\\-_.]+$";
      }
      mandatory true;
      description "Experiment identifier";
    }
    leaf repetitions {
      type uint64;
      description "Number of repetiotions (also called trails)";
    }
    leaf time-limit {
      type time-in-seconds;
      description "Runtime of a single experiment in seconds";
    }
    list probes {
      key "id";
      description "Probes to be used in this experiment";
      uses probe;
    }
    list parameters {
      key "id";
      description "Parameters (e.g. configurations) tested during an experiment";
      leaf id {
        type string{
          length "1..255";
          pattern "^[a-z0-9\\-_.]+$";
        }
        description "Identifier";
      }
      choice node-ref {
        case vnf {
          container vnf-ref {
            description "Reference to a VNF of the SUT.";
            uses vendor-name-version-id-ref;
          }
        }
        case probe {
            leaf probe-ref {
                type leafref {
                  path "../../probes/id";
                }
                description "Reference to a probe ID.";
            }
        }
        mandatory true;
        description "Either reference a VNF (vendor.name.version) or a probe (leafref)";
      }
      // parameters to actually configure the node:
      uses node-command-parameter;
      uses node-resource-parameter;
    }
  }

  grouping ped {
    description
      "Performance Experiment Descriptor (PED)";
    leaf id {
      type string{
        length "1..255";
        pattern "^[a-z0-9\\-_.]+$";
      }
      description "PED identifier";
    }
    leaf descriptor-version {
      type decimal64{
        fraction-digits 1;
      }
      default 1.0;
      description "Version of the data model";
    }
    leaf vendor {
      type string{
        length "1..255";
        pattern "^[a-z0-9\\-_.]+$";
      }
      mandatory true;
      description "PED vendor";
    }
    leaf name {
      type string{
        length "1..255";
        pattern "^[a-z0-9\\-_.]+$";
      }
      mandatory true;
      description "PED name";
    }
    leaf version {
      type string{
        length "1..255";
        pattern "^[abv0-9\\-_.]+$";
      }
      mandatory true;
      description "PED version";
    }
    uses generic-description;
    leaf author {
      type string;
      description "Author of the described experiments";
    }
    list targets {
      key "id";
      min-elements 1;
      description "List of target SUTs against which the experiments are executed";  
      uses sut-ref;
    }
    list experiments {
      key "id";
      min-elements 1;
      description "";
      uses experiment;
    }
  }

  // ---
  // Main entrypoint of the model.
  // ---
  container ped-catalog {
    description
      "Performance Experiment Descriptor (PED) catalog.
      A collection of PEDs that can be empty.
      (This construct is needed to be aligned with RFC6020.
      Putting the PED description directly into the model wouldn't
      work, since a PED cannot be empty).";
    list peds {
      key "id";
      description "List of PEDs";  
      uses ped;
    }
  }
}
