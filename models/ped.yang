/*
*  Copyright (c) 2019 Manuel Peuster <manuel@peuster.de
*  Copyright (c) 2019 SONATA-NFV, 5GTANGO, Paderborn University
* ALL RIGHTS RESERVED.
*
* Licensed under the Apache License, Version 2.0 (the "License");
* you may not use this file except in compliance with the License.
* You may obtain a copy of the License at
*
*     http://www.apache.org/licenses/LICENSE-2.0
*
* Unless required by applicable law or agreed to in writing, software
* distributed under the License is distributed on an "AS IS" BASIS,
* WITHOUT WARRANTIES OR CONDITIONS OF ANY KIND, either express or implied.
* See the License for the specific language governing permissions and
* limitations under the License.
*
* Neither the name of the SONATA-NFV, 5GTANGO, Paderborn University
* nor the names of its contributors may be used to endorse or promote
* products derived from this software without specific prior written
* permission.
*
* This work has also been performed in the framework of the 5GTANGO project,
* funded by the European Commission under Grant number 761493 through
* the Horizon 2020 and 5G-PPP programmes. The authors would like to
* acknowledge the contributions of their colleagues of the SONATA
* partner consortium (www.5gtango.eu).
*/

module ped
{
  namespace "https://github.com/sonata-nfv/tng-sdk-benchmark/models/ped";
  prefix "ped";

  revision 2019-02-21 {
    description
      "Initial revision. This YANG file defines
       the Performance Experiment Descriptor (PED)";
  }
  container ped-catalog {
    description
      "Performance Experiment Descriptor (PED)";

    leaf schema-version {
      description "Schema version for the PED. Uses v1.0 if not specified.";
      type string;
      default "v1.0";
    }

    leaf name {
      description "Name of the described experiments.";
      type string;
    }
  }
}
